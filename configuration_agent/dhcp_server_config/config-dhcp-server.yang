module config-dhcp-server { 
	namespace "http://netgroup.ipv6.polito.it/dhcp"; 
	prefix "dhcp";
	import ietf-inet-types { 
		prefix inet; 
	} 
	description "DHCP Server configuration"; 
	container server { 
		container globalIpPool { 
			container gatewayIp { 
				leaf gatewayIp { 
					description "Gateway IP Address"; 
					type inet:ipv4-address; 
				} 
				leaf gatewayMask { 
					description "Gateway IP Address Mask"; 
					type inet:ipv4-address; 
				} 
			} 
			container sections { 
				list section { 
					key "sectionStartIp"; 
					leaf sectionStartIp { 
						description "IP Address"; 
						type inet:ipv4-address; 
						mandatory "true"; 
					} 
					leaf sectionEndIp { 
						description "IP Address"; 
						type inet:ipv4-address; 
						mandatory "false"; 
					} 
				} 
			} 
			leaf defaultLeaseTime { 
				description "Specifies the lease time in seconds, option code is 51."; 
				type string; 
			} 
			leaf maxLeaseTime { 
				description "Specifies the lease time in seconds, option code is 51."; 
				type string;
			} 
			leaf domainNameServer { 
				description "Specifies the domain name server, option code is 5."; 
				type inet:ip-address; 
			} 
			leaf domainName { 
				description "Specifies the domain name, option code is 15.";type string;
			}
		}
		list clients {
			key "mac_address";
			leaf mac_address {
				type string;
			}
			leaf ip {
				type string;
			}
		}
	}
	container interfaces { 
		list ifEntry { 
			key "name"; 
			leaf name { 
				type string; 
			} 
			leaf address { 
				type inet:ip-address; 
			} 
			leaf configurationType { 
				type enumeration { 
					enum dhcp; 
					enum static; 
					enum not_defined;
				} 
			} 
			leaf type { 
				type enumeration { 
					enum dhcp; 
					enum config; 
					enum not_defined;
				} 
			}
			leaf default_gw { 
				type string; 
			}
		} 
	} 
}
