module config-firewall {
    namespace "http://netgroup.ipv6.polito.it/vnf";
    prefix "firewall";
    import ietf-inet-types { 
		prefix inet; 
	} 
    description "Firewall configuration";
	augment "/interfaces/ifEntry" { 
	    when "configurationType='static'"; 
	    leaf address { 
			type inet:ip-address; 
		}
	}

	container interfaces { 
		list ifEntry {
			key "name"; 
			leaf name { 
				type string; 
			}
			leaf configurationType { 
				type enumeration { 
					enum dhcp; 
					enum static;
					enum not_defined;
				} 
			} 
			leaf type { 
				type enumeration { 
					enum data; 
					enum config;
					enum not_defined;
				} 
			} 
		} 
	} 
       
	container firewall {
		list policy {
			key "policy-name";
			leaf policy-name {
				type string;
			}
			leaf description{
			    type string;
			}
			leaf action {
				type enumeration {
					enum drop;
					enum accept;
				}
			}
			leaf in-interface {
				type leafref {
				 	path "/interfaces/ifEntry/name";
				}
				mandatory false;
			}
			leaf out-interface {
				type leafref {
				 	path "/interfaces/ifEntry/name";
				}
				mandatory false;
			}
			leaf source-address {
				type inet:ip-address;
			}
			leaf source-mask {
				type inet:ip-address;
				mandatory false;
			}
			leaf destination-address {
				type inet:ip-address;
				mandatory false;
			}
			leaf destination-mask {
				type inet:ip-address;
				mandatory false;
			}
			leaf protocol {
				type enumeration {
					enum tcp;
					enum udp;
					enum icmp;
					enum all;
				}
			}
			leaf source-port {
				type string;
				mandatory false;
			}
			leaf destination-port {
				type string;
				mandatory false;
			}
		}
	}
 }
